# -*- coding: utf-8 -*-
# pocket_top_cover.FCMacro
# A plain, parametric laptop top cover: rounded rectangle + 7 screw holes.
# Nothing else. Built from scratch so every dimension is a parameter you can
# change, and the result is a live Part Design tree you can edit in the GUI.
#
# RUN:  Macro > Macros... > select this file > Execute.
# EDIT: change the numbers in PARAMETERS, or double-click a sketch in the tree.
# PRINT: after it builds, select the Body > File > Export > .stl or .step.

import math
import FreeCAD as App
import Part

# ============================ PARAMETERS =====================================
L        = 200.2    # length  X (mm)
W        = 125.8    # width   Y (mm)
R        = 7.417    # corner radius (mm)
T        = 1.5      # plate thickness (mm)
HOLE_D   = 2.2      # screw hole diameter (mm)

# screw holes, measured from the bott-left corner (x, y):
HOLES = [
    (5.402,   4.902), (68.502,  4.902), (131.752, 4.902), (194.802, 4.902),
    (5.402, 120.902), (194.802, 120.902), (100.102, 120.952),
]
# =============================================================================

doc = App.newDocument("TopCover")
body = doc.addObject("PartDesign::Body", "Body")

# grab the body's XY origin plane to attach sketches to
xy = None
for f in body.Origin.OriginFeatures:
    if "XY" in f.Label or "XY" in f.Name:
        xy = f
        break


def new_sketch(name):
    sk = doc.addObject("Sketcher::SketchObject", name)
    body.addObject(sk)
    if xy is not None:
        sk.AttachmentSupport = [(xy, "")]
        sk.MapMode = "FlatFace"
    return sk


# ---- outer profile: rounded rectangle (4 lines + 4 arcs) -------------------
V = App.Vector
Z = V(0, 0, 1)
out = new_sketch("Sketch_Outline")

lines_arcs = [
    ("line", V(R, 0, 0),       V(L - R, 0, 0)),                 # bottom
    ("arc",  V(L - R, R, 0),   -math.pi / 2, 0.0),              # BR corner
    ("line", V(L, R, 0),       V(L, W - R, 0)),                 # right
    ("arc",  V(L - R, W - R, 0), 0.0, math.pi / 2),             # TR corner
    ("line", V(L - R, W, 0),   V(R, W, 0)),                     # top
    ("arc",  V(R, W - R, 0),   math.pi / 2, math.pi),          # TL corner
    ("line", V(0, W - R, 0),   V(0, R, 0)),                     # left
    ("arc",  V(R, R, 0),       math.pi, 3 * math.pi / 2),      # BL corner
]
for spec in lines_arcs:
    if spec[0] == "line":
        out.addGeometry(Part.LineSegment(spec[1], spec[2]), False)
    else:
        _, center, a0, a1 = spec
        out.addGeometry(Part.ArcOfCircle(Part.Circle(center, Z, R), a0, a1), False)

# stitch the 8 segments end-to-end so the wire is closed (needed for Pad)
import Sketcher
n = out.GeometryCount
for i in range(n):
    out.addConstraint(Sketcher.Constraint("Coincident", i, 2, (i + 1) % n, 1))
doc.recompute()

pad = doc.addObject("PartDesign::Pad", "Plate")
pad.Profile = out
pad.Length = T
body.addObject(pad)
doc.recompute()

# ---- 7 screw holes ---------------------------------------------------------
hs = new_sketch("Sketch_Holes")
for (x, y) in HOLES:
    hs.addGeometry(Part.Circle(V(x, y, 0), Z, HOLE_D / 2.0), False)
doc.recompute()

pocket = doc.addObject("PartDesign::Pocket", "ScrewHoles")
pocket.Profile = hs
pocket.Reversed = True          # cut upward, through the plate
pocket.Length = T + 1.0         # a hair past the top face = clean through-holes
body.addObject(pocket)
doc.recompute()

# ---- chamfer the top perimeter edge (nicer feel, hides layer lines) --------
CHAMFER = 0.5  # mm

# IMPORTANT: select edges from pocket.Shape (the feature we're chamfering),
# not pad.Shape -- cutting the 7 holes renumbers every edge, so indices taken
# from the un-pocketed pad never match up with the pocketed body.
top_edge_names = []
for i, edge in enumerate(pocket.Shape.Edges):
    bb = edge.BoundBox
    flat_on_top = abs(bb.ZMin - T) < 1e-6 and abs(bb.ZMax - T) < 1e-6
    if not flat_on_top:
        continue
    # Both the straight sides and the big corner arcs are part of the outer
    # perimeter; the 7 hole rims are also flat circles at Z=T but much
    # smaller. A bounding-box-diagonal threshold cleanly tells them apart
    # (holes ~3.1mm diagonal, corner arcs ~10.5mm, sides much larger).
    diag = math.hypot(bb.XLength, bb.YLength)
    if diag > 5.0:
        top_edge_names.append(f"Edge{i + 1}")

if not top_edge_names:
    raise RuntimeError(
        "No perimeter edges matched for the chamfer -- check T and R against "
        "the actual model, or chamfer the top face manually in the GUI."
    )

chamfer = doc.addObject("PartDesign::Chamfer", "TopChamfer")
chamfer.Base = (pocket, top_edge_names)
chamfer.Size = CHAMFER
body.addObject(chamfer)
doc.recompute()

try:
    import FreeCADGui as Gui
    Gui.activeDocument().activeView().viewIsometric()
    Gui.SendMsgToActiveView("ViewFit")
except Exception:
    pass

App.Console.PrintMessage(
    "\nTop cover built: %.1f x %.1f x %.1f mm, %d holes Ø%.1f.\n"
    "Edit dimensions in the PARAMETERS block and re-run, or double-click a "
    "sketch to reshape it.\n" % (L, W, T, len(HOLES), HOLE_D))
