# -*- coding: utf-8 -*-
# pocket-bottom-cover-heft.FCMacro
#
# The laptop bottom cover (fit-critical 199.8 x 125.8 plateau, 6 screw holes)
# fused onto a wide, thick "heft" base that lowers the centre of mass and widens
# the footprint so a heavy top-flow cooler won't tip the machine over.
#
# Built as ONE parametric Part Design Body:
#   Sketch_Base    -> Pad "Base"        (wide heft slab, below the cover)
#   Sketch_Cover   -> Pad "Cover"       (fit-critical plateau that seats in the laptop)
#   LeadInChamfer  -> Chamfer           (45deg printable lead-in)  [FILLETS toggle]
#   FilletBottom   -> Fillet            (lap-contact edge, blends off the chamfer)
#   FilletTopLip   -> Fillet            (grip lip / shelf edge)    [FILLETS toggle]
#   Sketch_Screws  -> Pocket "Screws"   (6 holes through base+cover)
#   Sketch_Cbores  -> Pocket "Cbores"   (head recess in base bottom)
#   Sketch_Ballast -> Pocket "Ballast"  (pour-in ballast cavity, printed as a grid of
#                                         small cells separated by standing ribs, not one
#                                         giant pocket -- see BALLAST_RIBS_X/Y below for
#                                         why)                     [BALLAST toggle]
#   Sketch_Lid     -> Pocket "LidRebate"(flush lid ledge)          [BALLAST toggle]
#
# TWO OPTIONS with clear on/off switches:  FILLETS  and  BALLAST  (below).
#
# Print orientation: base flat on the bed, cover pointing up. The bottom edge
# leads in at 45deg (printable) and the fillet blends out of it higher up, so
# the lap-contact edge is rounded without an unprintable overhang at layer 1.

import math
import FreeCAD as App
import Part
import Sketcher

# ============================ PARAMETERS =====================================
# ---- fit-critical cover (do not change unless the laptop opening changes) ----
L        = 199.8     # cover length X (mm)
W        = 125.8     # cover width  Y (mm)
R        = 7.417     # cover corner radius
COVER_T  = 1.5       # cover thickness
HOLE_D   = 2.2       # screw hole diameter
HOLES = [(5.402,   5.402), (100.152, 5.402),   (194.852, 5.402),
         (5.402, 120.452), (100.152, 120.452), (194.852, 120.452)]

# ---- heft base ----
BASE_T      = 8.0    # base slab thickness (more = heavier + deeper ballast)
OVER_LR     = 20.0   # base overhang beyond cover, left & right each
OVER_FRONT  = 25.0   # base overhang beyond cover, front (-Y)
OVER_BACK   = 49.0   # base overhang beyond cover, back  (+Y, under the cooler)
BASE_R      = 10.0   # base corner radius (bigger than cover = comfier corners)

# ---- screw head bore through the base ----
# The screws are a CLEARANCE fit -- their threads engage the laptop standoff, not
# this part. So the narrow 2.2mm section must only be as long as the screw expects
# to pass through plastic: COVER_T (1.5mm), exactly like the bare cover. Making the
# 4.5mm bore run the FULL base thickness leaves precisely COVER_T of narrow hole
# above it, so your existing cover-length screws reach the standoff. Tied to BASE_T
# so it stays correct if the base thickness ever changes.
# (Printed base-down, the 4.5->2.2 neck bridges at the base/cover line -- a small
#  ~1.15mm annular overhang, usually fine. For a flush FLAT-HEAD screw with no
#  bridge at all, ask for a conical countersink instead.)
CBORE_D     = 4.5     # clearance for the M2 head + a small driver (raise if tight)
CBORE_DEPTH = BASE_T  # full base -> narrow hole above = COVER_T, matching the cover

# ============================ OPTION 1: FILLETS ==============================
FILLETS       = True    # <<< on/off switch for the comfort fillets
FILLET_BOTTOM = 3.0     # bottom outer edge radius (rests on lap) -- the big win
CHAMFER_LEAD  = 2.0     # 45-deg lead-in at the very bottom, UNDER the fillet.
                        # A plain fillet on a bottom edge starts near-horizontal
                        # at the plate (unprintable overhang). This 45-deg lead-in
                        # prints cleanly, and the fillet blends tangentially out of
                        # it -- rounded feel up top, printable 45 deg at the base.
FILLET_TOP    = 1.5     # top outer shelf-lip radius (faces up, plain fillet is fine)

# ============================ OPTION 2: BALLAST =============================
BALLAST       = False    # <<< on/off switch for the pour-in ballast cavity
BALLAST_MARGIN= 10.0    # wall left between cavity and base edges
BALLAST_FLOOR = 1.2     # material left between cavity top and the cover
BALLAST_LID   = 1.5     # depth/thickness of the flush lid rebate
LID_LIP       = 2.0     # how far the lid ledge extends past the cavity wall
# Cavity defaults to the BACK shelf (clear of all screws, under the cooler).
#
# The cavity ceiling (BALLAST_FLOOR, ~1mm) is an unsupported bridge over whatever the
# cavity's footprint is -- at the full ~220 x 36mm span this part defaults to, that's WAY
# past any FDM printer's bridging limit and would sag or fail outright, not just print a
# little rough like the small screw-hole bridges do. BALLAST_RIBS_X/Y leave thin printed
# walls standing inside the cavity, splitting one impossible bridge into a grid of small,
# easily-bridgeable ones. Ballast is poured in loose (shot/sand) so ribs don't defeat the
# purpose -- material just settles around them.
#   X = the part's longer axis (the ~220mm span -- needs more subdivision)
#   Y = the part's shorter axis (the ~36mm span -- needs less, or none)
# Defaults below target roughly <=17mm per unsupported span either way; tune for your
# printer/material. Setting either to 0 reproduces the original single-bridge behaviour
# on that axis.
BALLAST_RIBS_X = 10     # rib count dividing the long axis into (RIBS_X + 1) columns
BALLAST_RIBS_Y = 1      # rib count dividing the short axis into (RIBS_Y + 1) rows
BALLAST_RIB_W  = 3.0    # rib wall thickness (both axes)
BALLAST_CELL_R = 3.0    # corner radius per grid cell (clamped down for small cells)
# =============================================================================

bx0, bx1 = -OVER_LR, L + OVER_LR
by0, by1 = -OVER_FRONT, W + OVER_BACK

doc = App.newDocument("BottomCoverHeft")
body = doc.addObject("PartDesign::Body", "HeftBase")
V = App.Vector; Z = V(0, 0, 1)
xy = None
for f in body.Origin.OriginFeatures:
    if "XY" in f.Label or "XY" in f.Name:
        xy = f; break

def new_sketch(name, zoff=0.0):
    sk = doc.addObject("Sketcher::SketchObject", name); body.addObject(sk)
    if xy is not None:
        sk.AttachmentSupport = [(xy, "")]; sk.MapMode = "FlatFace"
        if zoff:
            pl = App.Placement(); pl.Base = V(0, 0, zoff); sk.AttachmentOffset = pl
    return sk

def add_rounded_rect(sk, x0, y0, x1, y1, r):
    i0 = sk.GeometryCount
    segs = [("line", V(x0+r,y0,0), V(x1-r,y0,0)), ("arc", V(x1-r,y0+r,0), -math.pi/2, 0.0),
            ("line", V(x1,y0+r,0), V(x1,y1-r,0)), ("arc", V(x1-r,y1-r,0), 0.0, math.pi/2),
            ("line", V(x1-r,y1,0), V(x0+r,y1,0)), ("arc", V(x0+r,y1-r,0), math.pi/2, math.pi),
            ("line", V(x0,y1-r,0), V(x0,y0+r,0)), ("arc", V(x0+r,y0+r,0), math.pi, 3*math.pi/2)]
    for s in segs:
        if s[0] == "line": sk.addGeometry(Part.LineSegment(s[1], s[2]), False)
        else: _, c, a0, a1 = s; sk.addGeometry(Part.ArcOfCircle(Part.Circle(c, Z, r), a0, a1), False)
    for k in range(8): sk.addConstraint(Sketcher.Constraint("Coincident", i0+k, 2, i0+(k+1)%8, 1))

def add_circles(sk, pts, dia):
    for (x, y) in pts: sk.addGeometry(Part.Circle(V(x, y, 0), Z, dia/2.0), False)

def pad(sketch, length, name, reversed=False):
    p = doc.addObject("PartDesign::Pad", name); p.Profile = sketch
    p.Length = length; p.Reversed = reversed
    body.addObject(p); doc.recompute(); return p

def pocket(sketch, length, name, reversed=False):
    p = doc.addObject("PartDesign::Pocket", name); p.Profile = sketch
    p.Length = length; p.Reversed = reversed
    body.addObject(p); doc.recompute(); return p

# ---- base slab (padded downward from XY) ----
sb = new_sketch("Sketch_Base", zoff=0.0)
add_rounded_rect(sb, bx0, by0, bx1, by1, BASE_R)
doc.recompute(); tip = pad(sb, BASE_T, "Base", reversed=True)   # z[-BASE_T, 0]

# ---- cover plateau (padded upward) ----
sc = new_sketch("Sketch_Cover", zoff=0.0)
add_rounded_rect(sc, 0, 0, L, W, R)
doc.recompute(); tip = pad(sc, COVER_T, "Cover")               # z[0, COVER_T]

# ---- fillets (done on the clean slab, before any holes) ----
def _outer_edge_names(zlvl):
    names = []
    for i, e in enumerate(tip.Shape.Edges):
        bb = e.BoundBox
        if abs(bb.ZMin-zlvl) < 1e-3 and abs(bb.ZMax-zlvl) < 1e-3:
            if (abs(bb.XMin-bx0) < 1e-2 or abs(bb.XMax-bx1) < 1e-2 or
                abs(bb.YMin-by0) < 1e-2 or abs(bb.YMax-by1) < 1e-2):
                names.append("Edge%d" % (i+1))
    return names

# fillet_outer/chamfer_outer used to be two near-identical copies of the same edge-select
# -> create-feature -> advance-tip logic, differing only in the PartDesign feature type and
# which property holds the size (Radius vs Size). Shared here as one helper.
def _outer_edge_feature(kind, name, zlvl, value):
    global tip
    names = _outer_edge_names(zlvl)
    if not names:
        App.Console.PrintWarning("%s: no matching edges, skipped.\n" % name); return
    try:
        f = doc.addObject("PartDesign::%s" % kind, name)
        f.Base = (tip, names)
        setattr(f, "Radius" if kind == "Fillet" else "Size", value)
        body.addObject(f); doc.recompute(); tip = f
    except Exception as ex:
        App.Console.PrintWarning("%s failed (%s) - lower the value or do it by "
                                 "hand.\n" % (name, str(ex)[:50]))

def fillet_outer(name, zlvl, rad):
    _outer_edge_feature("Fillet", name, zlvl, rad)

def chamfer_outer(name, zlvl, size):
    _outer_edge_feature("Chamfer", name, zlvl, size)

if FILLETS:
    # bottom edge: 45-deg chamfer lead-in first, then fillet the chamfer's top
    # edge -- OCC makes that fillet tangent to BOTH the 45-deg face and the wall,
    # so it flows 45deg -> curve -> vertical with no hard sub-edge between them.
    chamfer_outer("LeadInChamfer", -BASE_T, CHAMFER_LEAD)
    fillet_outer("FilletBottom", -BASE_T + CHAMFER_LEAD, FILLET_BOTTOM)
    # top lip faces up when printing base-down, so a plain fillet prints fine
    fillet_outer("FilletTopLip", 0.0, FILLET_TOP)

# ---- screw holes: through base + cover (sketch on top face, cut down) ----
ss = new_sketch("Sketch_Screws", zoff=COVER_T); add_circles(ss, HOLES, HOLE_D)
doc.recompute(); tip = pocket(ss, BASE_T + COVER_T + 1.0, "Screws")   # cuts -Z

# ---- counterbores: head recess in the base underside ----
if CBORE_DEPTH > 0:
    cb = new_sketch("Sketch_Cbores", zoff=-BASE_T); add_circles(cb, HOLES, CBORE_D)
    doc.recompute(); tip = pocket(cb, CBORE_DEPTH, "Cbores", reversed=True)  # cut +Z

# ---- ballast cavity + flush lid rebate (back shelf) ----
if BALLAST:
    cx0, cx1 = bx0 + BALLAST_MARGIN, bx1 - BALLAST_MARGIN
    cy0, cy1 = W + 3.0, by1 - BALLAST_MARGIN
    depth = BASE_T - BALLAST_FLOOR

    # grid of small pockets separated by BALLAST_RIB_W-thick standing walls, instead of
    # one giant pocket -- see the printability note above BALLAST_RIBS_X/Y.
    cols, rows = BALLAST_RIBS_X + 1, BALLAST_RIBS_Y + 1
    col_w = ((cx1 - cx0) - BALLAST_RIBS_X * BALLAST_RIB_W) / cols
    row_h = ((cy1 - cy0) - BALLAST_RIBS_Y * BALLAST_RIB_W) / rows
    if col_w <= 0 or row_h <= 0:
        raise RuntimeError("BALLAST_RIBS_X/Y too high (or BALLAST_RIB_W too wide) for the "
                            "cavity size -- cells would have zero or negative area.")
    cell_r = min(BALLAST_CELL_R, col_w / 2.0 - 0.1, row_h / 2.0 - 0.1)

    cav = new_sketch("Sketch_Ballast", zoff=-BASE_T)
    for i in range(cols):
        x0 = cx0 + i * (col_w + BALLAST_RIB_W)
        x1 = x0 + col_w
        for j in range(rows):
            y0 = cy0 + j * (row_h + BALLAST_RIB_W)
            y1 = y0 + row_h
            # add_rounded_rect(...,r=0) degenerates -- a zero-radius arc isn't valid
            # geometry -- so floor at a small imperceptible radius instead of exactly 0.
            add_rounded_rect(cav, x0, y0, x1, y1, max(cell_r, 0.05))
    doc.recompute(); tip = pocket(cav, depth, "Ballast", reversed=True)

    lid = new_sketch("Sketch_Lid", zoff=-BASE_T)
    add_rounded_rect(lid, cx0-LID_LIP, cy0-LID_LIP, cx1+LID_LIP, cy1+LID_LIP, 7.0)
    doc.recompute(); tip = pocket(lid, BALLAST_LID, "LidRebate", reversed=True)

body.Tip = tip
doc.recompute()
try:
    import FreeCADGui as Gui
    Gui.activeDocument().activeView().viewIsometric(); Gui.SendMsgToActiveView("ViewFit")
except Exception:
    pass

msg = ("\nHeft base built: %.0f x %.0f mm footprint, %.1f mm base + %.1f mm cover.\n"
       "  FILLETS: %s   BALLAST: %s\n"
       "  Screws now span base+cover -- use ~%.0f mm+ M2 screws (was %.1f mm).\n"
       % (bx1-bx0, by1-by0, BASE_T, COVER_T,
          "ON" if FILLETS else "off", "ON" if BALLAST else "off",
          BASE_T+COVER_T+4, COVER_T))
if BALLAST:
    # exact grid-cell volume (air only, ribs excluded) -- not the old bounding-box
    # estimate, which would now overcount by however much the ribs actually take up.
    cav_cc = cols * rows * col_w * row_h * (BASE_T - BALLAST_FLOOR) / 1000.0
    msg += ("  Ballast cavity ~%.0f cm3 (%dx%d cells, ribs excluded): "
            "~%.0f g steel shot or ~%.0f g sand.\n"
            % (cav_cc, cols, rows, cav_cc*4.5, cav_cc*1.6))
App.Console.PrintMessage(msg)
