# -*- coding: utf-8 -*-
# nh-l9-cover.FCMacro   (v2: chamfered grip, corner cable hooks)
#
# Parametric Part Design fan shroud that screws onto the Noctua NH-L9 fan.
# Body "Shroud":
#   Sketch_Posts      -> Pad     "Posts"        (4 corner standoffs, STANDOFF mm)
#   Sketch_Plate      -> Pad     "GridPlate"
#   (Chamfer)         -> Chamfer "GripChamfer"  (top+bottom perimeter, feels nice)
#   Sketch_Hooks      -> Pad     "Hooks"        (4 flat C-rings at the corners)
#   Sketch_Necks      -> Pad     "Necks"        (join hooks to the plate)
#   Sketch_HookMouths -> Pocket  "HookMouths"   (open each C so cables push in)
#   Sketch_GridHoles  -> Pocket  "GridHoles"    (hex airflow holes, <=10 mm)
#   Sketch_ScrewHoles -> Pocket  "ScrewHoles"
#
# Print orientation: grille top face DOWN on the bed. Posts and hooks then print
# upward with no supports; the flat hooks are coplanar with the plate top so they
# land flat on the plate too.
#
# The hooks are open C's sized for 3-5 mm cables (inner O8, mouth 4 mm). Chamfer
# note: OCC can't chamfer every edge on this part (the thin hook-mouth corners
# cap it near 0.15 mm, too small to feel), so this chamfers the top+bottom grip
# perimeter at 0.6 mm -- the edges you actually hold. Adjust CHAMFER as desired.

import math
import FreeCAD as App
import Part
import Sketcher

# ============================ PARAMETERS =====================================
FAN_SIZE    = 92.0     # corrected: real fan measures 92x92 (was 95.2, wrong)
FAN_CORNER  = 5.0
SCREW_DX    = 41.25    # corrected: standard 92mm fan hole spacing = 82.5x82.5
SCREW_DY    = 41.25    # (was 42.79/44.0, i.e. 85.6x88.0 -- too wide). If your
                        # calipers say something other than 82.5mm apart,
                        # set SCREW_DX=SCREW_DY=(measured_spacing/2) instead.
SCREW_D     = 4.5
POST_D      = 9.0
STANDOFF    = 0.5      # standoff height
GRID_T      = 2.5
CHAMFER     = 0.1      # grip-edge chamfer. 0.6 repeatedly failed to build on
                        # this geometry (with or without extra Tangent constraints
                        # on Sketch_Plate -- tried both, no reliable fix found).
                        # 0.1 is the confirmed-working value; too thin to really
                        # feel, but harmless to leave in. If a future revision
                        # increases GRID_T (plate thickness) rather than FAN_SIZE,
                        # a larger CHAMFER is more likely to succeed -- the limit
                        # seems tied to plate thickness vs. FAN_CORNER, not footprint.

HOLE_D      = 8.0      # airflow holes (<= 10)
PITCH       = 10.5
GRID_AREA_R = 38.5

# --- corner cable hooks (flat, coplanar with the plate top) ---
HOOK_IN     = 4.0      # inner radius (O8 cavity -> holds 3-5 mm cables)
HOOK_OUT    = 5.2      # outer radius
HOOK_MOUTH  = 4.0      # mouth opening width
HOOK_GAP    = 3.0      # how far the hook centre sits beyond the plate corner
NECK_W      = 5.0
NECK_LEN    = 4.5
# =============================================================================

assert HOLE_D <= 10.0
SCREWS = [( SCREW_DX,  SCREW_DY), (-SCREW_DX,  SCREW_DY),
          ( SCREW_DX, -SCREW_DY), (-SCREW_DX, -SCREW_DY)]
POST_KEEP = POST_D/2 + 2.0
half = FAN_SIZE/2.0
SQRT2 = math.sqrt(2.0)

def grid_holes():
    pts=[]; row_h=PITCH*math.sqrt(3)/2.0
    nrow=int(GRID_AREA_R/row_h)+2; ncol=int(GRID_AREA_R/PITCH)+2
    for r in range(-nrow,nrow+1):
        y=r*row_h; xoff=(PITCH/2.0) if (r%2) else 0.0
        for c in range(-ncol,ncol+1):
            x=c*PITCH+xoff
            if math.hypot(x,y)>GRID_AREA_R: continue
            if any(math.hypot(x-sx,y-sy)<POST_KEEP+HOLE_D/2 for sx,sy in SCREWS): continue
            pts.append((x,y))
    return pts

def corners():
    for sx,sy in [(1,1),(-1,1),(1,-1),(-1,-1)]:
        phi=math.atan2(sy,sx)
        Cx=sx*(half+HOOK_GAP/SQRT2); Cy=sy*(half+HOOK_GAP/SQRT2)
        yield phi,Cx,Cy

def rot(px,py,ang,ox,oy):
    c,s=math.cos(ang),math.sin(ang)
    return (ox+px*c-py*s, oy+px*s+py*c)

doc=App.newDocument("NH_L9_Cover")
body=doc.addObject("PartDesign::Body","Shroud")
V=App.Vector; Z=V(0,0,1)
xy=None
for f in body.Origin.OriginFeatures:
    if "XY" in f.Label or "XY" in f.Name: xy=f; break

def new_sketch(name,zoff=0.0):
    sk=doc.addObject("Sketcher::SketchObject",name); body.addObject(sk)
    if xy is not None:
        sk.AttachmentSupport=[(xy,"")]; sk.MapMode="FlatFace"
        if zoff:
            pl=App.Placement(); pl.Base=V(0,0,zoff); sk.AttachmentOffset=pl
    return sk

def add_rounded_rect(sk,x0,y0,x1,y1,r):
    i0=sk.GeometryCount
    segs=[("line",V(x0+r,y0,0),V(x1-r,y0,0)),("arc",V(x1-r,y0+r,0),-math.pi/2,0.0),
          ("line",V(x1,y0+r,0),V(x1,y1-r,0)),("arc",V(x1-r,y1-r,0),0.0,math.pi/2),
          ("line",V(x1-r,y1,0),V(x0+r,y1,0)),("arc",V(x0+r,y1-r,0),math.pi/2,math.pi),
          ("line",V(x0,y1-r,0),V(x0,y0+r,0)),("arc",V(x0+r,y0+r,0),math.pi,3*math.pi/2)]
    for sg in segs:
        if sg[0]=="line": sk.addGeometry(Part.LineSegment(sg[1],sg[2]),False)
        else: _,c,a0,a1=sg; sk.addGeometry(Part.ArcOfCircle(Part.Circle(c,Z,r),a0,a1),False)
    for k in range(8): sk.addConstraint(Sketcher.Constraint("Coincident",i0+k,2,i0+(k+1)%8,1))

def add_quad(sk,pts):
    i0=sk.GeometryCount
    for k in range(4):
        a=pts[k]; b=pts[(k+1)%4]
        sk.addGeometry(Part.LineSegment(V(a[0],a[1],0),V(b[0],b[1],0)),False)
    for k in range(4): sk.addConstraint(Sketcher.Constraint("Coincident",i0+k,2,i0+(k+1)%4,1))

def add_circles(sk,pts,dia):
    for (x,y) in pts: sk.addGeometry(Part.Circle(V(x,y,0),Z,dia/2.0),False)

def pad(sketch,length,name):
    p=doc.addObject("PartDesign::Pad",name); p.Profile=sketch; p.Length=length
    body.addObject(p); doc.recompute(); return p

def pocket(sketch,length,name):
    p=doc.addObject("PartDesign::Pocket",name); p.Profile=sketch
    p.Reversed=True; p.Length=length; body.addObject(p); doc.recompute(); return p

# ---- posts ----
posts=new_sketch("Sketch_Posts",zoff=0.0); add_circles(posts,SCREWS,POST_D)
doc.recompute(); pad(posts,STANDOFF,"Posts")

# ---- plate ----
plate=new_sketch("Sketch_Plate",zoff=STANDOFF)
add_rounded_rect(plate,-half,-half,half,half,FAN_CORNER)
doc.recompute(); plate_pad=pad(plate,GRID_T,"GridPlate")

# ---- chamfer the grip perimeter (top + bottom of the plate) ----
try:
    names=[]
    for i,e in enumerate(plate_pad.Shape.Edges):
        bb=e.BoundBox
        if bb.ZLength<1e-6 and math.hypot(bb.XLength,bb.YLength)>20.0:
            if abs(bb.ZMax-(STANDOFF+GRID_T))<1e-3 or abs(bb.ZMax-STANDOFF)<1e-3:
                names.append("Edge%d"%(i+1))
    if names:
        ch=doc.addObject("PartDesign::Chamfer","GripChamfer")
        ch.Base=(plate_pad,names); ch.Size=CHAMFER
        body.addObject(ch); doc.recompute()
except Exception as e:
    App.Console.PrintWarning("Grip chamfer skipped (%s) - try lowering CHAMFER "
                             "(e.g. 0.3, then 0.1) and re-running, or chamfer the "
                             "top/bottom perimeter by hand in the GUI.\n"%str(e)[:60])

# ---- hooks: washers + necks, then open the mouth ----
hooks=new_sketch("Sketch_Hooks",zoff=STANDOFF)
for phi,Cx,Cy in corners():
    hooks.addGeometry(Part.Circle(V(Cx,Cy,0),Z,HOOK_OUT),False)
    hooks.addGeometry(Part.Circle(V(Cx,Cy,0),Z,HOOK_IN),False)
doc.recompute(); pad(hooks,GRID_T,"Hooks")

necks=new_sketch("Sketch_Necks",zoff=STANDOFF)
for phi,Cx,Cy in corners():
    x_in=-(HOOK_OUT+NECK_LEN); x_out=-(HOOK_IN-1.0); w=NECK_W/2.0
    local=[(x_in,-w),(x_out,-w),(x_out,w),(x_in,w)]
    add_quad(necks,[rot(px,py,phi,Cx,Cy) for px,py in local])
doc.recompute(); pad(necks,GRID_T,"Necks")

mouths=new_sketch("Sketch_HookMouths",zoff=STANDOFF)
for phi,Cx,Cy in corners():
    x0=0.0; x1=HOOK_OUT+1.0; w=HOOK_MOUTH/2.0
    local=[(x0,-w),(x1,-w),(x1,w),(x0,w)]
    add_quad(mouths,[rot(px,py,phi,Cx,Cy) for px,py in local])
doc.recompute(); pocket(mouths,GRID_T+0.2,"HookMouths")

# ---- airflow holes ----
gh=new_sketch("Sketch_GridHoles",zoff=STANDOFF); add_circles(gh,grid_holes(),HOLE_D)
doc.recompute(); pocket(gh,GRID_T+0.2,"GridHoles")

# ---- screw holes ----
sc=new_sketch("Sketch_ScrewHoles",zoff=0.0); add_circles(sc,SCREWS,SCREW_D)
doc.recompute(); screw_pocket = pocket(sc,STANDOFF+GRID_T+0.2,"ScrewHoles")

body.Tip = screw_pocket   # show the finished solid by default, not the feature history
doc.recompute()
try:
    import FreeCADGui as Gui
    Gui.activeDocument().activeView().viewIsometric(); Gui.SendMsgToActiveView("ViewFit")
except Exception: pass
App.Console.PrintMessage("\nShroud v2 built: %.1f mm standoffs, %d airflow holes, "
    "4 corner cable hooks, %.1f mm grip chamfer.\n"%(STANDOFF,len(grid_holes()),CHAMFER))
