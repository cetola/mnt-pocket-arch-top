# -*- coding: utf-8 -*-
# nh-l9-cover.FCMacro
# A parametric fan shroud / grille that screws onto the Noctua NH-L9 fan using
# its 4 corner mounting holes. Built as a Part Design Body from sketches:
#
#   Body "Shroud"
#     Sketch_Plate      -> Pad  "GridPlate"   (rounded square top plate)
#     Sketch_Posts      -> Pad  "Posts"       (4 corner standoffs to the fan)
#     Sketch_GridHoles  -> Pocket "GridHoles" (hex array of airflow holes, <=10mm)
#     Sketch_ScrewHoles -> Pocket "ScrewHoles"(4 clearance holes through posts)
#
# Origin is the fan centre; Z=0 is the fan's top mounting face, shroud built up.
#
# !! VERIFY SCREW SPACING against your physical fan before printing !!
# SCREW_DX/DY below are measured from the supplied STEP model (85.6 x 88.0 mm
# overall). A standard 92 mm fan is nominally 82.5 x 82.5 mm (SCREW_DX=SCREW_DY
# =41.25). The converted model may have drift, so check with calipers and set
# these two numbers to match reality -- the screws must line up.

import math
import FreeCAD as App
import Part
import Sketcher

# ============================ PARAMETERS =====================================
FAN_SIZE    = 95.2     # fan frame outer size (square)
FAN_CORNER  = 5.0      # plate corner radius
SCREW_DX    = 42.79    # screw hole half-spacing in X  (see note above!)
SCREW_DY    = 44.0     # screw hole half-spacing in Y
SCREW_D     = 4.5      # screw clearance hole diameter
POST_D      = 9.0      # corner standoff post diameter
STANDOFF    = 5.0      # gap between fan top and plate underside (airflow + blade clearance)
GRID_T      = 2.5      # plate thickness

HOLE_D      = 8.0      # airflow hole diameter  (MUST be <= 10)
PITCH       = 10.5     # centre-to-centre spacing of the hex grid
GRID_AREA_R = 41.0     # radius of the holed region (leaves a solid rim)
# =============================================================================

assert HOLE_D <= 10.0, "HOLE_D must be <= 10 mm per requirement"

SCREWS = [( SCREW_DX,  SCREW_DY), (-SCREW_DX,  SCREW_DY),
          ( SCREW_DX, -SCREW_DY), (-SCREW_DX, -SCREW_DY)]
POST_KEEP = POST_D/2 + 2.0

# hex-packed airflow hole centres, clipped to a circle and clear of the posts
def grid_holes():
    pts = []
    row_h = PITCH*math.sqrt(3)/2.0
    nrow = int(GRID_AREA_R/row_h)+2
    ncol = int(GRID_AREA_R/PITCH)+2
    for r in range(-nrow, nrow+1):
        y = r*row_h
        xoff = (PITCH/2.0) if (r % 2) else 0.0
        for c in range(-ncol, ncol+1):
            x = c*PITCH + xoff
            if math.hypot(x, y) > GRID_AREA_R:
                continue
            if any(math.hypot(x-sx, y-sy) < POST_KEEP + HOLE_D/2 for sx, sy in SCREWS):
                continue
            pts.append((x, y))
    return pts

doc = App.newDocument("NH_L9_Cover")
body = doc.addObject("PartDesign::Body", "Shroud")
V = App.Vector
Z = V(0, 0, 1)

xy = None
for f in body.Origin.OriginFeatures:
    if "XY" in f.Label or "XY" in f.Name:
        xy = f
        break

def new_sketch(name, zoff=0.0):
    sk = doc.addObject("Sketcher::SketchObject", name)
    body.addObject(sk)
    if xy is not None:
        sk.AttachmentSupport = [(xy, "")]
        sk.MapMode = "FlatFace"
        if zoff:
            pl = App.Placement(); pl.Base = V(0, 0, zoff)
            sk.AttachmentOffset = pl
    return sk

def add_rounded_rect(sk, x0, y0, x1, y1, r):
    i0 = sk.GeometryCount
    segs = [
        ("line", V(x0+r, y0, 0),   V(x1-r, y0, 0)),
        ("arc",  V(x1-r, y0+r, 0), -math.pi/2, 0.0),
        ("line", V(x1, y0+r, 0),   V(x1, y1-r, 0)),
        ("arc",  V(x1-r, y1-r, 0), 0.0, math.pi/2),
        ("line", V(x1-r, y1, 0),   V(x0+r, y1, 0)),
        ("arc",  V(x0+r, y1-r, 0), math.pi/2, math.pi),
        ("line", V(x0, y1-r, 0),   V(x0, y0+r, 0)),
        ("arc",  V(x0+r, y0+r, 0), math.pi, 3*math.pi/2),
    ]
    for s in segs:
        if s[0] == "line":
            sk.addGeometry(Part.LineSegment(s[1], s[2]), False)
        else:
            _, c, a0, a1 = s
            sk.addGeometry(Part.ArcOfCircle(Part.Circle(c, Z, r), a0, a1), False)
    for k in range(8):
        sk.addConstraint(Sketcher.Constraint("Coincident", i0+k, 2, i0+(k+1) % 8, 1))

def add_circles(sk, pts, dia):
    for (x, y) in pts:
        sk.addGeometry(Part.Circle(V(x, y, 0), Z, dia/2.0), False)

def pad(sketch, length, name):
    p = doc.addObject("PartDesign::Pad", name)
    p.Profile = sketch; p.Length = length
    body.addObject(p); doc.recompute()
    return p

def pocket(sketch, length, name):
    p = doc.addObject("PartDesign::Pocket", name)
    p.Profile = sketch; p.Reversed = True; p.Length = length   # cut upward (+Z)
    body.addObject(p); doc.recompute()
    return p

# ---- corner posts (fan top -> plate underside) ----
posts = new_sketch("Sketch_Posts", zoff=0.0)
add_circles(posts, SCREWS, POST_D)
doc.recompute()
pad(posts, STANDOFF, "Posts")

# ---- top grille plate ----
half = FAN_SIZE/2.0
plate = new_sketch("Sketch_Plate", zoff=STANDOFF)
add_rounded_rect(plate, -half, -half, half, half, FAN_CORNER)
doc.recompute()
pad(plate, GRID_T, "GridPlate")

# ---- airflow holes through the plate ----
gh = new_sketch("Sketch_GridHoles", zoff=STANDOFF)
add_circles(gh, grid_holes(), HOLE_D)
doc.recompute()
pocket(gh, GRID_T + 0.2, "GridHoles")

# ---- screw clearance holes through posts + plate ----
sc = new_sketch("Sketch_ScrewHoles", zoff=0.0)
add_circles(sc, SCREWS, SCREW_D)
doc.recompute()
pocket(sc, STANDOFF + GRID_T + 0.2, "ScrewHoles")

doc.recompute()
try:
    import FreeCADGui as Gui
    Gui.activeDocument().activeView().viewIsometric()
    Gui.SendMsgToActiveView("ViewFit")
except Exception:
    pass

App.Console.PrintMessage(
    "\nShroud built: %d airflow holes at Ø%.1f mm, 4 screw holes at "
    "(+/-%.2f, +/-%.2f).\nVERIFY screw spacing against the real fan before "
    "printing.\n" % (len(grid_holes()), HOLE_D, SCREW_DX, SCREW_DY))
